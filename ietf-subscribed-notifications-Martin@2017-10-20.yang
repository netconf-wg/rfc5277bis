module ietf-subscribed-notifications {
  yang-version 1.1;
  namespace 
    "urn:ietf:params:xml:ns:yang:ietf-subscribed-notifications";

  prefix sn;

  import ietf-yang-types {
    prefix yang;
  }
  import ietf-inet-types {
    prefix inet;
  }
  import ietf-interfaces {
    prefix if;
  }

  organization "IETF";
  contact
    "WG Web:   <http:/tools.ietf.org/wg/netconf/>
     WG List:  <mailto:netconf@ietf.org>
     
     Editor:   Alexander Clemm
               <mailto:ludwig@clemm.org>

     Editor:   Eric Voit
               <mailto:evoit@cisco.com>
               
     Editor:   Alberto Gonzalez Prieto
               <mailto:agonzalezpri@vmware.com>

     Editor:   Einar Nilsen-Nygaard
               <mailto:einarnn@cisco.com>

     Editor:   Ambika Prasad Tripathy
               <mailto:ambtripa@cisco.com>";

  description
    "Contains a YANG specification for subscribing to events 
    and receiving matching content within notification messages.";
  
  revision 2017-10-20 {
    description
      "Initial version";
    reference 
      "draft-ietf-netconf-subscribed-notifications-06";
  }
  
  /*
   * FEATURES
   */
  
  feature json {
    description
      "This feature indicates that JSON encoding of notifications
       is supported.";
  }

  feature configured-subscriptions {
    description
      "This feature indicates that configuration of subscription is
      supported.";
  }
  
  feature replay {
    description
      "This feature indicates that historical event replay is 
      supported.  With replay, it is possible for past events to be 
      streamed in chronological order.";
  }
  
  /* 
   * EXTENSIONS
   */
   
  extension subscription-state-notif {
    description
      "This statement applies only to notifications. It indicates that 
       the notification is a subscription state notification. Therefore 
       it does not participate in a regular event stream and does not 
       need to be specifically subscribed to in order to receive 
       notifications.  This statement can only occur as a
       substatement to the 'notification' statement."; 
  }
  
  /*
   * IDENTITIES
   */

  
  /* Identities for subscription results */
  identity subscription-result {
    description
      "Base identity for RPC responses and State Change Notifications
      providing information on the creation, modification, deletion of 
       subscriptions.";
  }
  
  identity ok {
    base subscription-result;
    description
      "OK - RPC was successful and was performed as requested.";
  }
  
  identity error {
    base subscription-result;
    description
      "Problem with subscription.  Base identity for error return 
      codes for RPCs and State Change Notifications.";
  }

  /* Identities for subscription errors */
 
  identity suspension-timeout {
    base error;
    description
     "Termination of previously suspended subscription. The publisher 
      has eliminated the subscription as it exceeded a time limit for
      suspension.";
  }
  
  identity stream-unavailable {
    base error;
    description
     "Stream does not exist or is not available to the receiver.";
  }
  
  identity encoding-unavailable {
    base error;
    description
     "Encoding not supported";
  }
  
  identity replay-unsupported {
    base error;
    description
     "Replay cannot be performed for this subscription. The publisher 
     does not provide the requested historic information via replay.";
  }
  
  identity history-unavailable {
    base error;
    description
     "Replay request too far into the past. The publisher does store
      historic information for all parts of requested subscription, but
      not back to the requested timestamp.";
  }
  
  identity filter-unavailable {
    base error;
    description
     "Referenced filter does not exist";
  }
  
  identity filter-type-unsupported {
    base error;
    description
     "Publisher does not support filters constructed using this
     filtering technology syntax.";
  }
  
  identity filter-unsupported {
    base error;
    description
     "Failure can be from a syntax error, or a syntax too complex to be 
     processed by the platform. The supplemental info should include 
     the invalid part of the filter.";
  }
  
  identity namespace-unavailable {
    base error;
    description
     "Referenced namespace doesn't exist or is unavailable  
      to the receiver.";
  }
  
  identity no-such-subscription {
    base error;
    description
     "Referenced subscription doesn't exist. This may be as a result of 
      a non-existent subscription ID, an ID which belongs to another 
      subscriber, or an ID for acceptable subscription which has been
      statically configured.";
  }
  
  identity error-insufficient-resources {
    base error;
    description
      "The server has insufficient resources to support the
       subscription as requested by an RPC.";
  }
  
  identity unsupportable-volume {
    base error;
    description
      "The publisher cannot support the volume of information intended
      to be sent for an existing subscription.";
  }
  
  identity error-no-such-option {
    base error;
    description
      "A requested parameter setting is not supported.";
  }

  /* Identities for encodings */
  identity encodings {
    description
      "Base identity to represent data encodings";
  }
  
  identity encode-xml {
    base encodings;
    description
      "Encode data using XML";
  }
  
  identity encode-json {
    base encodings;
    description
      "Encode data using JSON";
  }

 
  /*
   * TYPEDEFs
   */

  typedef subscription-id {
    type uint32;
    description
      "A type for subscription identifiers.";
  }

  typedef filter-id {
    type string;
    description
      "A type to identify filters which can be associated with a 
       subscription.";
  }

  typedef subscription-result {
    type identityref {
      base subscription-result;
    }
    description
      "The result of a subscription operation";
  }

  typedef subscription-errors {
    type identityref {
      base error;
    }
    description
      "The reason for the failure of an RPC request or the sending  
       of a subscription suspension or termination notification";
  }  
  
  typedef encoding {
    type identityref {
      base encodings;
    }
    description
      "Specifies a data encoding, e.g. for a data subscription.";
  }
  
  typedef subscription-status {
    type enumeration {
      enum active {
        value 1;
        description
          "Status is active and healthy.";
      }
      enum inactive {
        value 2;
        description
          "Status is inactive, for example after the stop time, but not
          yet deleted from the configuration.";
      }
      enum suspended {
        value 3;
        description
          "The status is suspended, meaning that the publisher is 
          currently unable to provide the notification messages for the 
          subscription.";
        }
      enum in-error {
        value 4;
        description
          "The status is in error or degraded, meaning that stream and/
          subscription is currently unable to provide the negotiated
          notifications.";
      }
    }
    description
      "Specifies the status of a subscription.";
  }    

  typedef stream {
    type string;
    description
      "Specifies a system-provided datastream.";
  }

  typedef event-stream-filter-ref {
    type leafref {
      path "/sn:filters/sn:event-stream-filter/sn:identifier";
    }
    description
      "This type is used to reference an event filter.";
  }

  /*
   * GROUPINGS
   */
   
  grouping event-stream-filter-elements {
    description
      "This grouping defines the base for filters applied to event 
       streams.";
    choice filter-spec {
      description
        "The content filter specification for this request.";
      anydata subtree-filter {
        description
          "Event stream evaluation criteria encoded in a syntax of a
           supported type of an RFC 6241, Section 6 filter.  The subtree 
           filter is applied to the representation of individual, 
           delineated events as contained within the event stream.  For 
           example, if the notification message contains an instance of 
           a notification defined in YANG, then the top-level element is 
           the name of the YANG notification.  If the filter matches the
           information from the event stream, and the notification 
           message should be sent to the receiver(s).";
        reference "RFC 6241, Section 6.";
      }
      leaf xpath-filter {
        type yang:xpath1.0;
        description
          "Event stream evaluation criteria encoded in a syntax of xpath
           1.0 and applied against an event stream. The result of 
           applying XPath expression is converted to a boolean value
           using the standard XPath 1.0 rules.  If the boolean value is
           'true', the filter matches the information from the event
           stream, and the notification message should be sent to the 
           receiver(s).";
        reference "http://www.w3.org/TR/1999/REC-xpath-19991116";
      }
    }
  } 
   
  grouping subscription-policy-modifiable {
    description
      "This grouping describes all objects which may be changed
      in a subscription via an RPC.";  
    choice target {
      mandatory true;
      description
        "Identifies the source of information against which a 
        subscription is being applied, as well as specifics on the 
        subset of information desired from that source.  This choice 
        exists so that additional filter types can be added via 
        augmentation.";
      case stream {
        choice event-stream-filter {
          description
            "An event stream filter can be applied to a subscription.  
            That filter will come either referenced from a global list,  
            or be provided within the subscription itself.";
          case by-reference {
            description
              "Apply a filter that has been configured separately.";
            leaf event-stream-filter-ref {
              type event-stream-filter-ref;
              mandatory true;
              description
                "References an existing event-stream-filter which is to 
                be applied to stream for the subscription.";
            }
          }
          case within-subscription {
            description
              "Local definition allows a filter to have the same   
              lifecycle as the subscription.";
            uses event-stream-filter-elements;
          }
        }
      }
    }
    leaf stop-time {
      type yang:date-and-time;
      description
        "Identifies a time after which notifications for a subscription
        should not be sent.  If stop-time is not present, the
        notifications will continue until the subscription is
        terminated.  If replay-start-time exists, stop-time must for a
        subsequent time. If replay-start-time doesn't exist, stop-time
        must be for a future time.";
    }
  }
  
  grouping subscription-policy {
    description
      "This grouping describes information concerning a subscription.";
    leaf encoding {
      type encoding;
      default "encode-xml";
      description
        "The type of encoding for the subscribed data. Default is XML";
    }       
    uses subscription-policy-modifiable {
      augment target/stream {
        description
          "Adds additional objects which must be set just by RPC.";
        leaf stream {
          type stream;
          mandatory true;
          description
            "Indicates a stream of events against which to apply
            an event filter.";
        }
        leaf replay-start-time {
          if-feature "replay";
          type yang:date-and-time;
          description
            "Used to trigger the replay feature and indicate that the 
            replay should start at the time specified.  If 
            replay-start-time is not present, this is not a replay 
            subscription and event pushes should start immediately.  It 
            is never valid to specify start times that are later than 
            or equal to the current time.";
        }  
      }
    } 
  }
  
  grouping notification-origin-info {
    description
      "Defines the sender source from which notifications for a 
       configured subscription are sent.";
    choice notification-origin {
      description
        "Identifies the egress interface on the Publisher from which
         notifications will or are being sent.";
      case interface-originated {
        description
          "When the push source is out of an interface on the 
           Publisher established via static configuration.";
        leaf source-interface {
          type if:interface-ref;
          description
            "References the interface for notifications.";
        }
      }
      case address-originated {
        description
          "When the push source is out of an IP address on the 
           Publisher established via static configuration.";
        leaf source-vrf {
          type string;
          description
            "Network instance name for the VRF.  This could also have
            been a leafref to draft-ietf-rtgwg-ni-model, but that model 
            is not complete, and might not be implemented on a box.";
        }
        leaf source-address {
          type inet:ip-address-no-zone;
          description
            "The source address for the notifications.  If a source VRF
            exists, but this object doesn't, a publisher's default
            address for the VRF should be used.";
        }
      }
    }
  }

  grouping receiver-info {
    description
      "Defines where and how notification messages are pushed for one 
	  or more recipients.";
    container receivers {	
      description
        "One or more destinations for the notification messages which
		result from a subscription.";	  
	  list netconf {
	    key identifier;
	    description
		  "One on more receivers capable of handling notification
		  messages passed over NETCONF.";
        leaf identifier {
          type string;
		  description
		    "An identifier for a receiver reached using NETCONF.";
        }
        leaf ip {
          type inet:host;
          mandatory true;
		  description  
		   "Specifies the address used for notification messages to 
		    reach a receiver. One of the following must be specified: 
			an ipv4 address, an ipv6 address, or a host name.";
        }
        leaf port {
          type inet:port-number;
          default 830;
		  description
            "The NETCONF port number used for notification messages
            messages pushed to a receiver.";
        }
      }
      list http2 {
        key identifier;
	  	description
		  "One on more receivers capable of handling notification
		  messages passed over HTTP2.";
        leaf identifier {
          type string;
		  description
		    "An identifier for a receiver reached using HTTP2.";
        }
        leaf ip {
          type inet:host;
          mandatory true;
		  description  
		   "Specifies the address used for notification messages to 
		    reach a receiver. One of the following must be specified: 
			an ipv4 address, an ipv6 address, or a host name.";
        }
        leaf port {
          type inet:port-number;
          default 80;
		  description
            "The HTTP2 port number used for notification messages
            messages pushed to a receiver.";
        }
      }      
    }
  }	 

  grouping error-identifier {
    description
      "A code passed back within an RPC response to describe why the RFC
       has failed, or within a state change notification to describe why
       the change has occurred.";
    leaf error-id {
      type subscription-errors;
      mandatory true;
      description
        "Identifies the subscription error condition.";
    }
  }
    
  grouping hints {
    description
      "Objects passed back within an RPC response to describe why the 
       RFC has failed, or within a state change notification to 
       describe why the change has occurred.";
    leaf filter-failure { 
      type string;
      description
        "Information describing where and/or why a provided filter was
        unsupportable for a subscription.";
    }
  }
  
  grouping subscription-response-with-hints {
    description
      "Defines the output for the establish-subscription and
       modify-subscription RPCs.";
    leaf subscription-result {
      type subscription-result;
      mandatory true;
      description
        "Indicates whether subscription is operational, or if a problem
         was encountered.";
    }
    choice result {
      description
        "Depending on the subscription result, different data is 
         returned.";
      case no-success {
        description
          "This case applies when a subscription request was not
           successful and no subscription was created (or modified) as a
           result.  In this case, information MAY be returned that
           indicates suggested parameter settings that would have a 
           high likelihood of succeeding in a subsequent establish-
           subscription or modify-subscription request.";
        uses hints;
      }
    }
  }
  
  grouping notification-message-traffic {
    description
      "Operational data detailing measurements of pushed messages.";
    leaf pushed-notifications {
      type yang:counter64;
      description
        "Operational data which provides the number of update
         notifications pushed to a receiver.";
    } 
    leaf excluded-notifications {
      type yang:counter64;
      description
        "Operational data which provides the number of events
         from a stream explicitly removed via filtering so that 
         they are not sent to a receiver.";
    }
    leaf status {
      type subscription-status;
      mandatory true;
      description
        "Specifies the status of a subscription from the 
        perspective of a particular receiver.  With this info it 
        is possible to determine whether a subscriber is currently
        generating notification messages intended for that 
        receiver.";
	}
  }
   
  /*
   * RPCs
   */
   
  rpc establish-subscription {
    description
      "This RPC allows a subscriber to create (and possibly negotiate) 
       a subscription on its own behalf.  If successful, the 
       subscription remains in effect for the duration of the 
       subscriber's association with the publisher, or until the 
       subscription is terminated. In case an error (as indicated by 
       subscription-result) is returned, the subscription is not 
       created.  In that case, the RPC reply MAY include suggested
       parameter settings that would have a higher likelihood of 
       succeeding in a subsequent establish-subscription request.";
    input {
      uses subscription-policy;
    }
    output {
      uses subscription-response-with-hints  {
        augment "result" {
          description
            "Allows information to be passed back as part of a
             successful subscription establishment.";
          case success {
            description
              "This case is used when the subscription request was
               successful.";
            leaf identifier {
              type subscription-id;
              mandatory true;
              description
                "Identifier used for this subscription.";
            }
          }
        }
        augment "result/no-success" {
          description
            "Contains establish RPC specific objects which can be 
             returned as hints for future attempts.";
          leaf replay-start-time-hint {
            type yang:date-and-time;
            description
              "If a replay has been requested, but the requested replay
              time cannot be honored, this may provide a hint at an
              alternate time which may be supportable.";
          }
        }
      }
    }
  }
  
  rpc modify-subscription {
    description
      "This RPC allows a subscriber to modify a subscription that was
       previously created using establish-subscription.  If successful,
       the changed subscription remains in effect for the duration of 
       the subscriber's association with the publisher, or until the
       subscription is again modified or terminated.  In case an error 
       is returned (as indicated by subscription-result), the 
       subscription is not modified and the original subscription
       parameters remain in effect.  In that case, the rpc error 
       response MAY include suggested parameter hints that would have 
       a high likelihood of succeeding in a subsequent 
       modify-subscription request.";
    input {
      leaf identifier {
        type subscription-id;
        description
          "Identifier to use for this subscription.";
      }
      uses subscription-policy-modifiable;
    }
    output {
      uses subscription-response-with-hints;
    }
  }
  
  rpc delete-subscription {
    description
      "This RPC allows a subscriber to delete a subscription that
       was previously created from by that same subscriber using the 
       establish-subscription RPC.";
    input {
      leaf identifier {
        type subscription-id;
        mandatory true;
        description
          "Identifier of the subscription that is to be deleted.
           Only subscriptions that were created using
           establish-subscription can be deleted via this RPC.";
      }
    }
    output {
      leaf subscription-result {
        type subscription-result;
        mandatory true;
        description
          "Indicates whether subscription has been deleted, or if a 
          problem was encountered.";
      }
    }
  }
  
  rpc kill-subscription {
    description
      "This RPC allows an operator to delete a dynamic subscription 
      without restrictions on the originating subscriber or underlying 
      transport session.";
    input {
      leaf identifier {
        type subscription-id;
        mandatory true;
        description
          "Identifier of the subscription that is to be deleted. Only
            subscriptions that were created using establish-subscription
           can be deleted via this RPC.";
      }
    }
    output {
      leaf subscription-result {
        type subscription-result;
        mandatory true;
        description
          "Indicates whether subscription has been killed, or if a 
           problem was encountered.";
      }
    }
  }
  
  /*
   * NOTIFICATIONS
   */

  notification replay-completed {
    sn:subscription-state-notif;
    description
      "This notification is sent to indicate that all of the replay
        notifications have been sent. It must not be sent for any other
       reason.";
    leaf identifier {
      type subscription-id;
      mandatory true;
      description
        "This references the affected subscription.";
    }
  }
  
  notification subscription-completed {
    sn:subscription-state-notif;
    description
      "This notification is sent to indicate that a subscription has
       finished passing events.";
    leaf identifier {
      type subscription-id;
      mandatory true;
      description
        "This references the gracefully completed subscription.";
    }
  }

  notification subscription-started {
    sn:subscription-state-notif;
    description
      "This notification indicates that a subscription has started and
        notifications are beginning to be sent. This notification shall
       only be sent to receivers of a subscription; it does not 
       constitute a general-purpose notification.";
    leaf identifier {
      type subscription-id;
      mandatory true;
      description
        "This references the affected subscription.";
    }
    uses subscription-policy {
      refine "target/stream/replay-start-time" {
         description
           "Indicates the time that a replay using for the streaming of 
           buffered events.  This will be populated with the most recent
           of the following: replay-log-creation-time, replay-log-aged-
           time, replay-start-time, or the most recent publisher boot 
           time.";
      }
    }
  }
  
  notification subscription-resumed {
    sn:subscription-state-notif;
    description
      "This notification indicates that a subscription that had
       previously been suspended has resumed. Notifications will once
       again be sent.";
    leaf identifier {
      type subscription-id;
      mandatory true;
      description
        "This references the affected subscription.";
    }
  }
  
  notification subscription-modified {
    sn:subscription-state-notif;
    description
      "This notification indicates that a subscription has been 
       modified.  Notifications sent from this point on will conform to
       the modified terms of the subscription.  For completeness, this 
       notification includes both modified and non-modified aspects of 
       a subscription ";
    leaf identifier {
      type subscription-id;
      mandatory true;
      description
        "This references the affected subscription.";
    }
    uses subscription-policy;
  }
  
  notification subscription-terminated {
    sn:subscription-state-notif;
    description
      "This notification indicates that a subscription has been
       terminated.";
    leaf identifier {
      type subscription-id;
      mandatory true;
      description
        "This references the affected subscription.";
    }
    uses error-identifier;
    uses hints;
  }

  notification subscription-suspended {
    sn:subscription-state-notif;
    description
      "This notification indicates that a suspension of the
       subscription by the publisher has occurred.  No further
       notifications will be sent until the subscription resumes.
       This notification shall only be sent to receivers of a
       subscription; it does not constitute a general-purpose
       notification.";
    leaf identifier {
      type subscription-id;
      mandatory true;
      description
        "This references the affected subscription.";
    }
    uses error-identifier;
    uses hints;
  }

  /*
   * DATA NODES
   */

  container streams {
    config false;
    description
      "This container contains information on the built-in streams 
      provided by the publisher.";
    list stream {
      key "name";
      description
        "Identifies the built-in streams that are supported by the
         publisher.";
      leaf name {
        type stream;
        description
          "A handle for a sequential set of events, each of which 
           is characterized by its own domain and semantics.";
      }
      leaf description {
        type string;
        mandatory true;
        description
          "A description of the event stream, including such information 
           as the type of events that are sent over this stream.";
      }
      leaf replay-support {
        if-feature "replay";
        type empty;
        description
          "Indicates that event replay is available on this stream.";
      }
      leaf replay-log-creation-time {
        if-feature "replay";
        type yang:date-and-time;
        description
          "The timestamp of the creation of the log used to support the 
          replay function on this stream. Note that this might be 
          earlier then the earliest available notification in the log.  
          This object is updated if the log resets for some reason.  
          This object MUST be present if replay is supported.";
      }
      leaf replay-log-aged-time {
        if-feature "replay";
        type yang:date-and-time;
        description
          "The timestamp of the last notification aged out of the log. 
          This object MUST be present if replay is supported and any 
          notifications have been aged out of the log.";
      }
    }
  }
   
  container filters {
    description
      "This container contains a list of configurable filters
       that can be applied to subscriptions.  This facilitates
       the reuse of complex filters once defined.";
    list event-stream-filter {
      key "identifier";
      description
        "A list of pre-positioned filters that can be applied to
         event subscriptions.";
      leaf identifier {
        type filter-id;
        description
          "An identifier to differentiate between filters.";
      }
      uses event-stream-filter-elements;
    }
  }
  
  container subscription-config {
    if-feature "configured-subscriptions";
    description
      "Contains the list of subscriptions that are configured,
       as opposed to established via RPC or other means.";
    list subscription {
      key "identifier";
      description
        "Content of a subscription.";
      leaf identifier {
        type subscription-id;
        description
          "Identifier to use for this subscription.";
      }
      uses subscription-policy;
      uses receiver-info;
      uses notification-origin-info;
    }
  }
  container subscriptions {
    config false;
    description
      "Contains the list of currently active subscriptions, i.e.
       subscriptions that are currently in effect, used for subscription
       management and monitoring purposes. This includes subscriptions
       that have been setup via RPC primitives as well as subscriptions 
       that have been established via configuration.";
    list subscription {
      key "identifier";
      description
        "Content of a subscription. Subscriptions can be created using 
         a control channel or RPC, or be established through 
         configuration.";
      leaf identifier {
        type subscription-id;
        description
          "Identifier of a subscription; unique within a publisher";
      }
      leaf configured-subscription {
       if-feature "configured-subscriptions";
       type empty;
       description
         "The presence of this leaf indicates that the subscription
          originated from configuration, not through a control channel 
          or RPC.";
      }
      uses subscription-policy;
      uses notification-origin-info {
        if-feature "configured-subscriptions";
      }
      uses receiver-info {
        augment receivers/netconf {
          description
            "include operational data for NETCONF receivers.";
          uses notification-message-traffic;           
        }
		augment receivers/http2 {
          description
            "include operational data for HTTP2 receivers.";
          uses notification-message-traffic;         
        }
		augment receivers {
          description
            "include operational data for HTTP1.1 receivers.";       
          list http1.1 {
            key identifier;
    	  	description
    		  "One on more receivers capable of handling notification
	    	  messages passed over HTTP1.1.";
			leaf identifier {
			  type string;
    		  description
    		    "An identifier for a receiver reached using HTTP2.";
            }
            leaf ip {
              type inet:host;
              mandatory true;
		      description  
		       "Specifies the address used for notification messages to 
		        reach a receiver. One of the following must be  
			    specified: an ipv4 address, an ipv6 address, or a host 
				name.";
            }
            leaf port {
              type inet:port-number;
              default 80;
		      description
                "The HTTP1.1 port number used for notification messages
                messages pushed to a receiver.";
            }
		    uses notification-message-traffic;
          }            
        }
      }
    }
  }
}
